module sonic-srv6 {
    revision 2024-12-05 {
		description
			"Initial revision.";
	}
    namespace "http://github.com/sonic-net/sonic-srv6";

    import ietf-yang-types {
		prefix yang;
	}

	import ietf-inet-types {
		prefix inet;
	}

	import sonic-common {
		prefix scommon;
	}

    container sonic-srv6 {
        scommon:db-name "CONFIG_DB";

        list SRV6_MY_SID_TABLE {
            key "ip-address";
			scommon:key-delim "|";
			scommon:key-pattern "SRV6_MY_SID_TABLE|{ip-address}";

            leaf ip-address {
                type inet:ipv6-address;
            }

            leaf block_len {
                type uint8 {
					range "1..128";
				}
                
                default 32;
            }

            leaf node_len {
                type uint8 {
					range "1..128";
				}

                default 16;
            }

            leaf func_len {
                type uint8 {
					range "1..128";
				}

                default 16;
            }

            leaf arg_len {
                type uint8 {
					range "1..128";
				}

                default 0;
            }

            leaf action {
                type enumeration {
                    enum uN;
                    enum uDT6;
                    enum uDT46;
                }
            }

            leaf dscp_mode {
                type enumeration {
                    enum uniform;
                    enum pipe;
                }
                when "../action = uDT6 or ../action = uDT46]";
            }
        }
    }
}
