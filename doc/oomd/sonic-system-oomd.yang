module sonic-system-oomd {
    namespace "http://github.com/Azure/sonic-oomd";
    prefix soomd;
    yang-version 1.1;

    revision 2022-01-18 {
        description "Initial revision.";
    }
    
    container sonic-system-oomd {

        typedef terminate_scope_type {
            type enumeration {
                enum process;
                enum session;
            }
        }

        container oomd {
            container policies {
                leaf enable_memory_monitor {
                    type boolean;
                    description "OOMD memory monitor enable status";
                    default true;
                }
                leaf enable_container_monitor {
                    type boolean;
                    description "OOMD memory monitor enable status";
                    default true;
                }
                leaf high_water_mark {
                    description "Free memory high-water mark in MB";
                    default 400;
                    type uint32;
                }
                leaf low_water_mark {
                    description "Free memory low-water mark in MB";
                    default 600;
                    type uint32;
                }
                leaf domain_account {
                    type boolean;
                    description "OOMD will terminate process run by domain account";
                    default true;
                }
                leaf restart_container {
                    type boolean;
                    description "OOMD will monitor and restart container when container OOM";
                    default true;
                }
                leaf manage_container {
                    type boolean;
                    description "OOMD will terminate non-critical process run inside container";
                    default true;
                }
                leaf terminate_scope {
                    type terminate_scope_type;
                    description "OOMD will terminate process or session";
                    default process;
                }
                list allow_user_list {
                    key name;
                    description "User name list";
                    leaf name {
                        type string;
                    }
                }
                list allow_group_list {
                    key name;
                    description "Group name list";
                    leaf name {
                        type string;
                    }
                }
            }
        }
    }
}
