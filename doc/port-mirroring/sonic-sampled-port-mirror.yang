module sonic-mirror-session {

    yang-version 1.1;

    namespace "http://github.com/sonic-net/sonic-mirror-session";
    prefix sms;

    import ietf-inet-types {
        prefix inet;
    }

    import sonic-port {
        prefix port;
    }

    import sonic-policer {
        prefix policer;
    }

    description
        "SONiC Mirror session yang model";

    revision 2026-04-14 {
        description
            "Add sample_rate and truncate_size leaves for sampled port mirroring
             with truncation support.";
    }

    revision 2021-06-15 {
        description
            "Initial revision.";
    }

    typedef session_type {
        type enumeration {
            enum ERSPAN {
                description "ERSPAN session";
            }
            enum SPAN {
                description "SPAN session";
            }
        }
    }

    typedef session_direction {
        type enumeration {
            enum RX {
                description "RX direction";
            }
            enum TX {
                description "TX direction";
            }
            enum BOTH {
                description "Both RX and TX direction";
            }
        }
    }

    container sonic-mirror-session {

        container MIRROR_SESSION {

            list MIRROR_SESSION_LIST {
                key "name";

                leaf name {
                    type string {
                        pattern '[a-zA-Z0-9]{1}([-a-zA-Z0-9_]{0,31})';
                        length 1..32 {
                            error-message "Invalid mirror session name";
                            error-app-tag session-name-invalid;
                        }
                    }
                    description
                        "Mirror session name.";
                }

                leaf type {
                    type session_type;
                    default "ERSPAN";
                    description
                        "Mirror session type.";
                }

                leaf src_ip {
                    when "current()/../type = 'ERSPAN'";
                    must "(contains(current(), ':') and contains(../dst_ip, ':')) or (not(contains(current(), ':')) and not(contains(../dst_ip, ':')))" {
                        error-message "src_ip and dst_ip must have the same IP version.";
                    }
                    type inet:ip-address;
                    description
                        "ERSPAN source ip. This IP will be set as source ip in
                        outer header of mirrored frame ";
                }

                leaf dst_ip {
                    when "current()/../type = 'ERSPAN'";
                    must "(contains(current(), ':') and contains(../src_ip, ':')) or (not(contains(current(), ':')) and not(contains(../src_ip, ':')))" {
                        error-message "src_ip and dst_ip must have the same IP version.";
                    }
                    type inet:ip-address;
                    description
                        "ERSPAN destination ip. Mirrored frames will be routed to this destination.
                        This IP will be set as destination ip in outer header of mirrored frame ";
                }

                leaf gre_type {
                    when "current()/../type = 'ERSPAN'";
                    type string {
                        pattern "0[xX][0-9a-fA-F]*|([0-9]|[1-5]?[0-9]{2,4}|6[1-4][0-9]{3}|65[1-4][0-9]{2}|655[1-2][0-9]|6553[0-5])";
                        length 1..6 {
                            error-message "Invalid GRE type";
                            error-app-tag gre-type-invalid;
                        }
                    }
                    default 0x88be;
                    description
                        "ERSPAN outer header GRE type.";
                }

                leaf dscp {
                    when "current()/../type = 'ERSPAN'";
                    type uint8 {
                        range "0..63" {
                            error-message "Invalid dscp value";
                            error-app-tag dscp-invalid;
                        }
                    }
                    description
                        "ERSPAN outer header DSCP value. Mirrored frames will be sent with configured DSCP value";
                }

                leaf ttl {
                    when "current()/../type = 'ERSPAN'";
                    type uint8 {
                        range "0..255" {
                            error-message "Invalid TTL value";
                            error-app-tag ttl-invalid;
                        }
                    }
                    description
                        "ERSPAN outer header TTL value. Mirrored frames will be sent with configured TTL value";
                }

                leaf queue {
                    type uint8;
                    description
                        "ERSPAN Queue. Mirrored frames will be sent to this queue";
                }

                leaf dst_port {
                    when "current()/../type = 'SPAN'";
                    type union {
                        type leafref {
                            path "/port:sonic-port/port:PORT/port:PORT_LIST/port:name";
                        }
                        type string {
                            pattern "CPU";
                        }
                    }
                    description
                        "Destination port configuration for port mirroring(SPAN).";
                }

                leaf src_port {
                    type string {
                        length 1..2048;
                    }
                    description
                        "Source port configuration for mirroring. Can be configured for both SPAN/ERSPAN.
                        Supports both port and port-channel as arguments";
                }

                leaf direction {
                    type session_direction;
                    default "BOTH";
                    description
                        "Direction configuration for mirroring. Can be configured for both SPAN/ERSPAN.
                        Supports rx/tx/both as direction config.
                           RX: Captures frames ingressing on source port.
                           TX: Captures frames egressing on source port.
                           BOTH: Captures frames ingressing or egressing on source port.";
                }

                leaf policer {
                    type leafref {
                        path "/policer:sonic-policer/policer:POLICER/policer:POLICER_LIST/policer:name";
                    }
                    description
                        "Policer to be applied for the mirrored traffic.";
                }
                
                leaf sample_rate {
                    when "current()/../type = 'ERSPAN'";
                    type uint32 {
                        range "0|256..8388608" {
                            error-message "Sample rate must be 0 (no sampling/full mirroring) or 256-8388608";
                            error-app-tag sample-rate-invalid;
                        }
                    }
                    default 0;
                    description
                        "Sampling rate for mirrored packets. 0 means full mirroring
                         (no sampling). N means mirror 1 out of every N packets.";
                }

                leaf truncate_size {
                    when "current()/../type = 'ERSPAN'";
                    type uint32 {
                        range "0|64..9216" {
                            error-message "Truncate size must be 0 (no truncation) or 64-9216 bytes";
                            error-app-tag truncate-size-invalid;
                        }
                    }
                    default 0;
                    description
                        "Truncation size in bytes for mirrored packets.
                         0 means no truncation. When set, only the first N bytes
                         of each mirrored packet are sent.";
                }
            }
        }
    }
}
