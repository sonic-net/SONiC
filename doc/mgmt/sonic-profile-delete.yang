module sonic-profile-delete {
	namespace "http://github.com/Azure/sonic-acl";
	prefix sacl;
	yang-version 1.1;

	import ietf-yang-types {
		prefix yang;
	}

	import sonic-common {
		prefix scommon;
	}

	organization
		"SONiC";

	contact
		"SONiC";

	description
		"SONIC PROFILE DELETE";

	revision 2022-07-22 {
		description
			"Initial revision.";
	}

	container sonic-profile-delete {

		list PROFILE_DELETE {
			key "itemkey";

			leaf itemkey {
				type string;
			}
		}
	}
}
